# Requirements

## #1: Doors (Functional)

### #2: Doors Opening Outside (Functional)
Once the lift has arrived to the floor called. The system shall open the doors within 10 seconds.

### #4: Door Closing Manual (Functional)
If the close door button is pressed, the system shall run object detection and close the doors within 5 sec.

### #5: Door Opening Manual (Functional)
If the open door button is pressed. The system shall ensure the lift is currently at floor destination, and will open the doors.

### #6: Door Closing Automatic (Functional)
Once the lift has arrived at destined floor, the system shall run object detection

## #7: Floors (Functional)
