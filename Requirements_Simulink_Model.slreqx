# Requirements_Simulink_Model

## #1: Movement of lift (Functional)

### #2 (Functional)
system only moves when doors are fully closed

### #3: Moving Up (Functional)

#### #6 (Functional)
system moves up if button pressed is higher than current floor value

#### #7 (Functional)
system moves up if called externally from a higher floor

### #4: Moving Down (Functional)

#### #8 (Functional)
system moves down if button pressed is lower than current floor value

#### #9 (Functional)
system moves down if called externally from a lower floor

### #5: Idle (Functional)

#### #10 (Functional)
system is idle if there is no input/backlog

## #11: Operation Of Doors (Functional)

### #12: Opening doors (Functional)

#### #17 (Functional)
system only opens doors when stationary

#### #18 (Functional)
system opens doors automatically in 3 seconds when it has reached the requested floor

#### #19 (Functional)
system opens doors if the ‘open door’ button is pressed and the lift is at a requested floor

### #13: Closing doors (Functional)

#### #20 (Functional)
system closes doors automatically after 10 seconds of being fully open

#### #21 (Functional)
system takes 3 seconds to close doors

#### #22 (Functional)
system closes doors if the ‘close door’ button is pressed and no objects are detected

### #14: Object detection (Functional)

#### #23 (Functional)
system keeps doors open if object is detected by the sensors

#### #24 (Functional)
while the doors are closing, system opens doors immediately if an object is detected by the sensors

### #15: Idle (Functional)

#### #25 (Functional)
system keeps doors closed while in idle state

## #26: Logic (Functional)

## #27: Emergency State (Functional)

### #28 (Functional)
system goes into the emergency state when the ‘stop’ button is pressed

### #29 (Functional)
when in emergency state, system stops the lift’s movement

### #30 (Functional)
when in emergency state, system plays the audio command

## #31: Interface (Functional)

### #32: Interior Interface (Functional)

#### #36 (Functional)
system has buttons corresponding to floors -1 to 8

#### #37 (Functional)
system has a ‘stop’ button

#### #38 (Functional)
system has a close doors button

#### #39 (Functional)
system has an open doors button

#### #40 (Functional)
system displays the lift’s position

#### #41 (Functional)
system turns on a light to indicate the lift is moving

### #33: Exterior Interface (Functional)

#### #42 (Functional)
system has an up button on every floor, except on the top floor

#### #43 (Functional)
system has a down button on every floor, except on the bottom floor

#### #44: Lift’s movement view (Functional)

##### #46 (Functional)
indicates the current position

##### #47 (Functional)
indicates direction of movement

#### #45 (Functional)
system has a light to indicate the request button was pressed

### #34: Audio (Functional)

#### #48: Music (Functional)

##### #51 (Functional)
system continuously plays music inside the lift

#### #49: Audio commands (Functional)

##### #52 (Functional)
active when doors are opening

##### #53 (Functional)
active when doors are closing

##### #54 (Functional)
active when stopping at a floor

#### #50: Alarm (Functional)

##### #55 (Functional)
system uses it when in the emergency state/or when doors are open too long

##### #56 (Functional)
active when exceeding weight limit

### #35: Buttons (Functional)

#### #57 (Functional)
each button has braille text on it

#### #58 (Functional)
the buttons use high contrasting colours between background and text

#### #59 (Functional)
the numbered buttons are 50x50mm

#### #60 (Functional)
emergency button has to be bright red with block letters

## #61: Physical attributes (Functional)

### #62: Service (Functional)

#### #67 (Functional)
system should be able to provide a minimum of 40 years of service

#### #68 (Functional)
system should work for 5 years without being serviced

### #63: Capacity (Functional)

#### #69 (Functional)
system should be able to hold a maximum of 5 passengers / 375kg

#### #70 (Functional)
system alerts if this condition is exceeded

### #64: Travel (Functional)

#### #71 (Functional)
system should travel at 3m/s at maximum speed

#### #72 (Functional)
system should slow down when approaching the requested floor

### #65: Dimensions (Functional)

#### #73 (Functional)
the lift car should have dimensions of 1500x2000x2500mm

#### #74 (Functional)
the cabin should have around 2.5m^2 of floor space

#### #75 (Functional)
lift’s entrance has a width of at least 900mm

#### #76 (Functional)
internal button interface begins no further than 900mm above the floor

#### #77 (Functional)
internal button interface ends no further than 1200mm above the floor

#### #78 (Functional)
external call buttons are 1200mm above the ground

### #66: Motor (Functional)

#### #79 (Functional)
the lift cabin has a mass of 1200kg

#### #80 (Functional)
the motor has to have a peak torque of 3600Nm

#### #81 (Functional)
the voltage input should be

#### #82 (Functional)
the amperage input should be
