# Requirements

## #1: Doors (Functional)

### #2: Doors Opening Outside (Functional)
Once the lift has arrived to the floor called. The system shall open the doors within 10 seconds.

### #4: Door Closing Manual (Functional)
If the close door button is pressed, the system shall run object detection and close the doors within 5 sec.

### #5: Door Opening Manual (Functional)
If the open door button is pressed. The system shall ensure the lift is currently at floor destination, and will open the doors.

### #6: Door Closing Automatic (Functional)
Once the lift has arrived at destined floor, the system shall run object detection

## #7: Req Floor (Functional)
The system shall order the floor commands, such that they are either in ascending or descending order

## #10: Cur Floor (Functional)

## #11: Equal (Functional)
The system shall stop when on the correct floor, when the current floor is equal to the requested floor
